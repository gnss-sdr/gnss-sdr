-- SPDX-License-Identifier: BSD-1-Clause
-- SPDX-FileCopyrightText: (c) 2003, 2004 Lev Walkin <vlm@lionet.info>. All rights reserved.
SUPL-END DEFINITIONS AUTOMATIC TAGS ::=
BEGIN

EXPORTS SUPLEND;

IMPORTS StatusCode, Position, Ver
          FROM ULP-Components;

SUPLEND ::= SEQUENCE {
  position    Position OPTIONAL,
  statusCode  StatusCode OPTIONAL,
  ver         Ver OPTIONAL,
  ...}

END
